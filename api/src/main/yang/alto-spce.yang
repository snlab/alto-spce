module alto-spce {
    yang-version 1;
    namespace "urn:opendaylight:alto:spce";
    prefix "alto-spce";

    import ietf-inet-types {prefix inet;}

    organization "SNLab.";
    contact "Jensen Zhang <jingxuan.zhang@gmail.com>";

    revision "2015-11-06" {
        description "Initial revision of alto-spce model. The model is based
        on PCEP (https://tools.ietf.org/rfc/rfc5440.txt) but with simplifications.
        A key simplification is that it does not specify whether it is re-optimization
        or a new request. We expect the next version to fix the issue.";
    }

    typedef error-code-type {
        type enumeration {
            enum OK;
            enum ERROR;
        }
    }

    typedef alto-spce-metric {
        type enumeration {
            enum bandwidth;
            enum hopcount;
        }
    }

    grouping endpoint-group {
        container endpoint {
            leaf src {
                type inet:ipv4-address;
                mandatory true;
                description "Source IP address";
            }
            leaf dst {
                type inet:ipv4-address;
                mandatory true;
                description "Destination IP address";
            }
        }
    }

    rpc alto-spce-setup {
        description "Given the endpoints, this service computes a path
           satisfying the constraints; among those satisfying the constraints, 
           it computes the one with the best object metrics. If a path is 
           found, the service will setup the path by installing flow rules 
           in FRM. This service does not handle the complexity of re-route.";

        input {
            uses endpoint-group;

            leaf-list objective-metrics {
                type alto-spce-metric;
            }
            list constraint-metric {
                leaf metric {
                    type alto-spce-metric;
                }
                leaf min {
                    type uint64;
                    description "We use min and max to allow more flexible range spec.";
                }
                leaf max {
                    type uint64;
                }
            }
        }

        output {
           leaf path {
               type string;
           }
           leaf error-code {
               type error-code-type;
           }
        }
    }

    rpc alto-spce-remove {
        input {
            leaf path {
                type string;
            }
        }

        output {
            leaf error-code {
                type error-code-type;
            }
        }
    }


    rpc rate-limiting-setup {
        description "Given the path (source IP and destination IP are all included), and the value of the rate limiting,
            this service will set the meter with the rate limiting value, and update every related
            flow entries in switches along this path.";

        input {
            uses endpoint-group;

            leaf limited-rate {
                description "The metric is kbps.";
                type int32;
            }

            leaf burst-size {
                description "The metric is kb. The smaller value means rate limiting is more fine grain";
                type int32;
            }
        }

        output {
           leaf path {
               type string;
           }
           leaf error-code {
               type error-code-type;
           }
        }
    }

    rpc rate-limiting-update {
        description "Given the path (source IP and destination IP are all included), and the value of the rate limiting,
            this service will set the meter with the rate limiting value, and update every related
            flow entries in switches along this path.";

        input {
            uses endpoint-group;

            leaf limited-rate {
                description "The metric is kbps.";
                type int32;
            }

            leaf burst-size {
                description "The metric is kb. The smaller value means rate limiting is more fine grain";
                type int32;
            }
        }

        output {
           leaf path {
               type string;
           }
           leaf error-code {
               type error-code-type;
           }
        }
    }

    rpc rate-limiting-remove {
        input {
            leaf path {
                type string;
            }
        }

        output {
            leaf error-code {
                type error-code-type;
            }
        }
    }

    rpc get-path {
        input {
            uses endpoint-group;
        }

        output {
           leaf path {
               type string;
           }
           leaf bandwidth {
               type int32;
           }
           leaf burst_size {
               type int32;
           }
           leaf error-code {
               type error-code-type;
           }
        }
    }

    rpc get-tp-bandwidth-map {
        output {
            leaf tp-bandwidth-map{
                type string;
            }
            leaf error-code {
                type error-code-type;
            }
        }
    }

    rpc get-bandwidth-topology {
        output {
            leaf tpid-map {
                type string;
            }
            leaf bandwidth-topology {
                type string;
            }
            leaf error-code {
                type error-code-type;
            }
        }
    }

    rpc add-flow-to-switch {
        input {
            leaf switch-id {
                type string;
            }
        }
        output {
            leaf error-code {
                type error-code-type;
            }
        }
    }

    rpc remove-all-flows-to-switch {
        input {
            leaf switch-id {
                type string;
            }
        }
        output {
            leaf error-code {
                type error-code-type;
            }
        }
    }


}
