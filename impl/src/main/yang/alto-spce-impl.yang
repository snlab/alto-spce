module alto-spce-impl {
    yang-version 1;
    namespace "urn:opendaylight:alto:spce";
    prefix "alto-spce-impl";

    import config { prefix config; revision-date 2013-04-05; }
    import opendaylight-md-sal-binding { prefix md-sal-binding; revision-date 2013-10-28;}

    description
        "Service definition for alto-spce project";

    revision "2014-12-10" {
        description
            "Initial revision";
    }

    identity alto-spce {
        base config:module-type;
        config:java-name-prefix AltoSpce;
    }

    augment "/config:modules/config:module/config:configuration" {
        case alto-spce {
            when "/config:modules/config:module/config:type = 'alto-spce'";
            container broker {
                uses config:service-ref {
                    refine type {
                        mandatory true;
                        config:required-identity md-sal-binding:binding-broker-osgi-registry;
                    }
                }
            }
        }
    }
}
