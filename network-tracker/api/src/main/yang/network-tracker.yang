module network-tracker {
    yang-version 1;
    namespace "urn:opendaylight:params:xml:ns:yang:network-tracker";
    prefix "network-tracker";

    revision "2015-11-07" {
        description "Initial revision of network-tracker model";
    }

    rpc alto-spce-get-tx-bandwidth {
        description "";

        input {
            leaf tp-id {
                type string;
            }
        }

        output {
           leaf speed {
               type uint64;
           }
        }
    }

    rpc alto-spce-get-tx-speed {
        description "";

        input {
            leaf tp-id {
                type string;
            }
        }

        output {
           leaf speed {
               type uint64;
           }
        }
    }

    rpc alto-spce-get-rx-speed {
        description "";

        input {
            leaf tp-id {
                type string;
            }
        }

        output {
           leaf speed {
               type uint64;
           }
        }
    }
}
